module sonic-xcvrd-log {
    namespace "http://github.com/sonic-net/sonic-xcvrd-log";
    prefix xcvrd_log;
    yang-version 1.1;

    organization
        "SONiC";

    contact
        "SONiC";

    description
        "SONiC DualToR xcvrd logging configuration data";

    revision 2024-10-14 {
        description
            "Initial revision";
    }

    container sonic-xcvrd-log {

        container XCVRD_LOG {

            container Y_CABLE {

                leaf log_verbosity {
                    type enumeration {
                        enum info;
                        enum notice;
                        enum debug;
                        enum warning;
                        enum critical;
                    }

                    description "xcvrd log verbosity level. ";

                }

            }
        }
    }
}
