module sonic-tc-dscp-map {

    yang-version 1.1;

    namespace "http://github.com/Azure/sonic-tc-dscp-map";

    prefix tcdscpm;

    import sonic-extension {
        prefix sonic-ext;
    }

    organization
        "SONiC";

    contact
        "SONiC";

    description
        "TC_TO_DSCP_MAP yang Module for SONiC OS";

    revision 2021-04-15 {
        description
            "Initial revision.";
    }

    container sonic-tc-dscp-map {   

        container TC_TO_DSCP_MAP {

            description "TC_TO_DSCP_MAP part of config_db.json";

            list TC_TO_DSCP_MAP_LIST {

                key "name";

                //sonic-ext:map-list true; //special conversion for map tables
                //sonic-ext:map-leaf "tc dscp"; //every key:value pair is mapped to list keys, e.g. "1":"7" ==> tc=1, dscp=7

                leaf name {
                    type string {
                        pattern '[a-zA-Z0-9]{1}([-a-zA-Z0-9_]{0,31})';
                        length 1..32 {
                            error-message "Invalid length for map name.";
                            error-app-tag map-name-invalid-length;
                        }
                    }
                }

                list TC_TO_DSCP_MAP { //this is list inside list for storing mapping between two fields
                    key "tc dscp";

                    leaf tc {
                        type string {
                            pattern "[0-9]?" {
                                error-message "Invalid Traffic Class";
                                error-app-tag tc-invalid;
                            }
                        }
                    }

                    leaf dscp {
                        type string {
                            pattern "([0-9]|[1-5][0-9]|6[0-3])?" {
                                error-message "Invalid DSCP";
                                error-app-tag dscp-invalid;
                            }
                        }
                    }
                }
            }
        }
    }
}
