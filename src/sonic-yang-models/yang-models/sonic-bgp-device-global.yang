module sonic-bgp-device-global {
    namespace "http://github.com/sonic-net/sonic-bgp-device-global";
    prefix bgp_device_global;
    yang-version 1.1;

    organization
        "SONiC";

    contact
        "SONiC";

    description
        "SONIC Device-specific BGP global data";

    revision 2024-01-28 {
        description "Add Weighted ECMP using BGP link bandwidth";
    }

    revision 2022-06-26 {
        description "Initial revision";
    }

    container sonic-bgp-device-global {

        container BGP_DEVICE_GLOBAL {

            description "BGP_DEVICE_GLOBAL part of config_db.json";

            container STATE {

                description "BGP device-specific global data";

                leaf tsa_enabled {
                    type boolean;
                    default "false";
                    description
                    "When set to true, Traffic is shifted away (TSA), i.e, BGP routes are not advertised to neighboring routers";
                }

                leaf wcmp_enabled {
                    description "Enables/Disables Weighted-Equal Cost-Multipath using BGP link bandwidth";
                    type boolean;
                    default "false";
                }

                leaf idf_isolation_state {
                    description "Configures device IDF isolation state";
                    type enumeration {
                        enum isolated_no_export {
                            description "IDF isolated using no-export community tag";
                        }
                        enum isolated_withdraw_all {
                            description "IDF isolated by withdrawing routes";
                        }
                        enum unisolated {
                            description "IDF un-isolated";
                        }
                    }
                    default "unisolated";
                }

                leaf received_bandwidth {
                    description "Configures device received-bandwidth state";
                    type enumeration {
                        enum ignore {
                            description "Ignore link bandwidth (i.e., do regular ECMP, not weighted)";
                        }
                        enum allow {
                            description "Allow for normal behavior without bgp bestpath bandwidth";
                        }
                        enum skip_missing {
                            description "Ignore paths without link bandwidth for W-ECMP (if other paths have it)";
                        }
                        enum default_weight_for_missing {
                            description "Assign a low default weight (value 1) to paths not having link bandwidth";
                        }
                    }
                    default "ignore";
                }

            }
            /* end of STATE container */
        }
        /* end of BGP_DEVICE_GLOBAL container */
    }
    /* end of container sonic-bgp-device-global */
}
/* end of module sonic-bgp-device-global */
