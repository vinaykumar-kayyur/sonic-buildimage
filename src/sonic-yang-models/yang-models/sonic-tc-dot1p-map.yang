module sonic-tc-dot1p-map {

    yang-version 1.1;

    namespace "http://github.com/Azure/sonic-tc-dot1p-map";

    prefix tcdot1pm;

    import sonic-extension {
        prefix sonic-ext;
    }

    organization
        "SONiC";

    contact
        "SONiC";

    description
        "TC_TO_DOT1P_MAP yang Module for SONiC OS";

    revision 2021-04-15 {
        description
            "Initial revision.";
    }

    container sonic-tc-dot1p-map {  

        container TC_TO_DOT1P_MAP {

            description "TC_TO_DOT1P_MAP part of config_db.json";

            list TC_TO_DOT1P_MAP_LIST {

                key "name";

                //sonic-ext:map-list true; //special conversion for map tables
                //sonic-ext:map-leaf "tc dot1p"; //every key:value pair is mapped to list keys, e.g. "1":"7" ==> tc=1, dot1p=7

                leaf name {
                    type string {
                        pattern '[a-zA-Z0-9]{1}([-a-zA-Z0-9_]{0,31})';
                        length 1..32 {
                            error-message "Invalid length for map name.";
                            error-app-tag map-name-invalid-length;
                        }
                    }
                }

                list TC_TO_DOT1P_MAP { //this is list inside list for storing mapping between two fields

                    key "tc dot1p";

                    leaf tc {
                        type string {
                            pattern "[0-9]?" {
                                error-message "Invalid Traffic Class";
                                error-app-tag tc-invalid;
                            }
                        }
                    }

                    leaf dot1p {
                        type string {
                            pattern "[0-7]?" {
                                error-message "Invalid DOT1P";
                                error-app-tag dot1p-invalid;
                            }
                        }
                    }
                }
            }
        }
    }
}
