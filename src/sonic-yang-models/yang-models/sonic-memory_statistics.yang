module memory-statistics {
    yang-version 1.1;

    namespace "http://github.com/sonic-net/sonic-memory-statistics";
    prefix mem;
    
    import sonic-types {
        prefix stypes;
    }
    
    description "Memory-Statistics YANG Module for SONiC-based OS";
    revision 2024-07-22 {
        description "First Revision";
    }
     
    container MemoryStatistics {
        description "Memory statistics configuration";

        leaf enabled {
            type boolean;
            default true;
            description "Enable or disable memory statistics";
        }

        leaf sampling-interval {
            type uint16;
            units "minutes";
            description "Interval for sampling memory statistics";
        }

        leaf retention-period {
            type uint16;
            units "days";
            description "Retention period for memory statistics data";
        }
    }
}
