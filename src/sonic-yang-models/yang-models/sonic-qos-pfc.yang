module sonic-qos-pfc {
    namespace "http://github.com/Azure/sonic-qos-pfc";
    prefix sonic-qos-pfc;

    yang-version 1.1;

    import sonic-port {
        prefix prt;
    }

    organization
        "SONiC";

    contact
        "SONiC";

    description
        "SONIC QoS Priority-based Flow Control";

    revision 2021-07-01 {
        description
            "Initial revision.";
    }

    container sonic-qos-pfc {
        container PFC_WD {
            list PFC_WD_LIST {
                key "ifname";
                leaf ifname {
                    type union {
                        type leafref {
                            path "/prt:sonic-port/prt:PORT/prt:PORT_LIST/prt:name";
                        }
                        type string {
                            pattern "GLOBAL" {
                                error-message "Invalid interface name";
                                error-app-tag interface-name-invalid;
                            }
                        }
                    }
                }
                leaf action {
                    must "../ifname != 'GLOBAL'";
                    type enumeration {
                        enum drop;
                        enum forward;
                        enum alert;
                    }
                    description
                        "PFC watchdog action when entering storm state.";
                }
                leaf detection_time {
                    must "../ifname != 'GLOBAL'";
                    type uint32 {
                        range 100..5000;
                    }
                    description
                        "Detection interval for pause storm in msec.";
                }
                leaf restoration_time {
                    must "../ifname != 'GLOBAL'";
                    type uint32 {
                        range 100..60000;
                    }
                    description
                        "Time delay before resuming normal PFC operation in msec.";
                }
                leaf POLL_INTERVAL {
                    must "../ifname = 'GLOBAL'";
                    type uint32 {
                        range 100..3000;
                    }
                    description
                        "Priority-based Flow Control global watchdog polling
                        interval in msec.";
                }
            }
        }
    }
}
