module sonic-stormond-config{

    yang-version 1.1;

    namespace "http://github.com/sonic-net/sonic-stormond-config";
    prefix stormond-config;

    import sonic-types {
        prefix stypes;
    }

    description "STORMOND_CONFIG Table yang Module for SONiC";

    container sonic-stormond-config {

        container STORMOND_CONFIG {

            description "stormond_config table in config_db.json";

            container INTERVALS {

                leaf daemon_polling_interval {
                    description "Polling inerval for Storage Monitoring Daemon in STORMOND_CONFIG table";
                    type string {
                        length 1..32;
                    }
                }

                leaf fsstats_sync_interval {
                    description "FSSTATS JSON file syncing interval for the Storage Monitoring Daemon in STORMOND_CONFIG table";
                    type string {
                        length 1..32;
                    }
                }
            }
        }
    }
}
