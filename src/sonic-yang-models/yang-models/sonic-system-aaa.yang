module sonic-system-aaa {
    namespace "http://github.com/Azure/sonic-system-aaa";
    prefix ssys;
    yang-version 1.1;

    import sonic-types {
        prefix stypes;
    }

    revision 2021-10-12 {
        description "Add AAA authorization/accounting support.";
    }

    revision 2021-04-15 {
        description "Initial revision.";
    }

    container sonic-system-aaa {
        container AAA {
            list AAA_LIST {
                key "type";

                leaf type {
                    type enumeration {
                        enum authentication;
                        enum authorization;
                        enum accounting;
                    }
                    description "AAA type authentication/authorization/accounting";
                }

                leaf login {
                    type string {
                        pattern 'radius|tacacs\+|local|default' {
                            error-message "Invalid login choice";
                        }
                    }
                    description "AAA authentication/authorization/accounting methods - radius/tacacs+/local/default";
                    default "local";
                }

                leaf failthrough {
                    type stypes:boolean_type;
                    description "When set to true, authentication is attempted on next configured server/local in the list upon failure.";
                    default False;
                }

                leaf fallback {
                    type stypes:boolean_type;
                    description "Allow AAA fallback";
                    default False;
                }
                
                leaf debug {
                    type stypes:boolean_type;
                    description "Enable/disable AAA debugging";
                    default False;
                }

                leaf trace {
                    type stypes:boolean_type;
                    description "AAA packet trace";
                    default False;
                }
            }
        }
    }
}
