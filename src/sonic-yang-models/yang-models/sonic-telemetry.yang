module sonic-telemetry {

    yang-version 1.1;

    namespace "http://github.com/sonic-net/sonic-telemetry";
    prefix telemetry;

    import ietf-inet-types {
        prefix inet;
    }

    organization
        "SONiC";

    contact
        "SONiC";

    description "TELEMETRY YANG Module for SONiC OS";

    revision 2022-05-13 {
        description "First Revision";
    }

    container sonic-telemetry {

        container TELEMETRY {

            description "TELEMETRY TABLE part of config_db.json";

            container certs {

                leaf ca_crt {
                    type string {
                        pattern '(/[a-zA-Z0-9_-]+)*/([a-zA-Z0-9_-]+).cer';
                    }
                    description "Local path for ca_crt.";
                }

                leaf server_crt {
                    type string {
                        pattern '(/[a-zA-Z0-9_-]+)*/([a-zA-Z0-9_-]+).cer';
                    }
                    description "Local path for server_crt.";
                }

                leaf server_key {
                    type string {
                        pattern '(/[a-zA-Z0-9_-]+)*/([a-zA-Z0-9_-]+).key';
                    }
                    description "Local path for server_key.";
                }

            }

            container gnmi {

                leaf client_auth {
                    type boolean;
                    description "Flag for requiring client auth.";
                }

                leaf log_level {
                    type uint8 {
                        range 0..100;
                    }
                    description "Log level for gnmi.";
                }

                leaf port {
                    type inet:port-number;
                    description "Port gnmi runs on.";
                }

            }

        }

        container TELEMETRY_CLIENT_CERT {
            description "TELEMETRY client cert list";

            list TELEMETRY_CLIENT_CERT_LIST {
                max-elements 8;
                key "cert_cname";

                leaf cert_cname {
                    type string;
                    description
                        "client cert common name";
                }

                leaf role {
                    type string;
                    mandatory true;
                    description
                        "role of client cert common name";
                }
            }
        }
    }
}
