module sonic-dhcp-server {

    yang-version 1.1;

    namespace  "http://github.com/Azure/sonic-dhcp-server";

    prefix dhcp-server;

    import ietf-inet-types {
        prefix inet;
    }

    import sonic-port {
        prefix port;
    }

    description "DHCP SERVER YANG module for SONiC OS";

    revision 2022-09-23 {
        description "Initial version";
    }

    container sonic-dhcp-server {

        container DHCP_SERVER {

            description "DHCP_SERVER part of config_db.json";

            list IPS_LIST {

                description "List of IPs in DHCP_SERVER Table";

                key "ip";

                leaf ip {
                    description "IP as DHCP_SERVER";
                    type inet:ipv4-address;
                }

                leaf expireat {
                    description "exire time for lease for this dhcp_server. Range with fraction-digits as 10: -922337203.6854775808 - 922337203.6854775807";
                    type decimal64 {
                        fraction-digits 10;
                    }
                }

                leaf ttl {
                    description "ttl for dhcp_server";
                    type decimal64 {
                        fraction-digits 4;
                        range "-100.999 .. 100.99";
                    }
                }


                leaf type {
                    description "REVIEW: is only hash allowed?";
                    type string {
                        pattern 'hash';
                    }
                }

                container value {
                    choice values {
                        case NULL {
                            leaf NULL {
                                type string {
                                    pattern "NULL";
                                }
                            }
                        }
                        case NAME_PORT {
                            leaf name {
                                type string {
                                }
                            }

                            leaf port {
                                description "PORT where dhcp server is reachable";
                                type leafref {
                                    path /port:sonic-port/port:PORT/port:PORT_LIST/port:name;
                                }
                            }
                        }
                    } /* end of choice values */

                }/* end of container value */

            }/* end of list IPS_LIST */

        } /* end of container DHCP_SERVER */

    } /* end of container sonic-dhcp-server */

} /* end of module sonic-dhcp-server */
