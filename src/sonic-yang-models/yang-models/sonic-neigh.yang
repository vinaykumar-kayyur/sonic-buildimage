module sonic-neigh {
	yang-version 1.1;
	namespace "http://github.com/sonic-net/sonic-neigh";
	prefix neigh;

	import ietf-inet-types {
		prefix inet;
	}

	import ietf-yang-types {
		prefix yang;
	}

	import sonic-vlan {
		prefix svlan;
	}

	organization "SONiC";
	contact "SONiC";

	description "NEIGH YANG Module for SONiC OS";

	revision 2023-03-31 {
		description "Initial Revision";
	}

	container sonic-neigh {
		container NEIGH {
			description "NEIGH configuration";
			list NEIGH_LIST {
				key "vlan neighbor";

				leaf vlan {
					description "Neighbor interface and IP address ex. Vlan1000|100.1.1.3";
					type leafref {
						path "/svlan:sonic-vlan/svlan:VLAN/svlan:VLAN_LIST/svlan:name";
					}
				}

				leaf neighbor {
					description "Neighbor interface and IP address ex. Vlan1000|100.1.1.3";
					type inet:ip-address;
				}

				leaf neigh {
					description "Neighbor MAC address";
					type yang:mac-address;
				}

				leaf family {
					description "IP family of Neighbor address";
					type string {
						pattern "IPv4|IPV4|IPv6|IPV6";
					}
				}
			}
		}
	}
}
