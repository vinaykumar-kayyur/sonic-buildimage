module sonic-versions {

    yang-version 1.1;

    namespace "http://github.com/Azure/sonic-versions";
    prefix versions;


    description "VERSIONS YANG Module for SONiC OS";

    revision 2020-04-10 {
        description "First Revision";
    }

    container sonic-versions {

        container VERSIONS {

            description "VERSIONS part of config_db.json";

            container DATABASE {

                leaf VERSION {
                    type string {
                        length 1..255;
                        pattern 'version_([1-9]|[1-9]{1}[0-9]{1})_([0-9]{1,2})_([0-9]{1,2})';
                    }
                }
            }
            /* end of container DATABASE */
        }
        /* end of container VERSIONS */
	}
	/* end of top level container */
}
/* end of module sonic-versions */
