module sonic-copp {

	yang-version 1.1;

	namespace "http://github.com/Azure/sonic-copp";
	prefix copp;
    
    import sonic-types {
		prefix stypes;
	}

	description "CoPP YANG Module for SONiC OS";

	revision 2021-03-31 {
		description
			"First Revision";
	}

	container sonic-copp {
		container COPP_GROUP {
			list COPP_GROUP_LIST {
				key name;

				leaf name {
					type string;
					description "Control plane policing group name";
				}

				leaf queue {
					type uint32;
                    default 0;
					description "CPU Rx queue id";
				}

				leaf trap_priority {
					type uint32;
                    default 0;
					description "Trap priority";
				}

				leaf trap_action {
                    mandatory true;
                    type stypes:copp_packet_action;
					description "Trap action";
				}
				
				leaf meter_type {
                    mandatory true;
                    type stypes:meter_type;
					description "Policer meter type";
				}
				
				leaf mode {
                    mandatory true;
                    type enumeration {
                        enum sr_tcm;
                        enum tr_tcm;
                        enum storm;
                    }
					description "Policer mode";
				}
				
				leaf color {
                    type enumeration {
                        enum blind;
                        enum color;
                    }
                    default "color";
					description "Policer color source";
				}

				leaf cir {
					type uint64;
                    default 0;
					description
						"Committed information rate for the dual-rate token
						bucket policer.  This value represents the rate at which 
						tokens are added to the primary bucket.";
				}

				leaf cbs {
                    must "((current()/../cir) and (current()/../cir > 0))" {
						error-message "cbs can't be configured without cir.";
					}
					must "(current() >= current()/../cir)" {
						error-message "cbs must be greater than or equal to cir";
					}
					type uint64;
                    default 0;
					description
						"Committed burst size for the dual-rate token bucket
						policer.  This value represents the depth of the token
						bucket.";

					must "((current()/../cir) and (current()/../cir > 0))" {
						error-message "cbs can't be configured without cir.";
					}
					must "(current() >= current()/../cir)" {
						error-message "cbs must be greater than or equal to cir";
					}
				}

				leaf pir {
                    when "current()/../mode = 'tr_tcm'";
					must "((current()/../cir) and (current()/../cir > 0))" {
						error-message "pir can't be configured without cir.";
					}
					must "(current() >= current()/../cir)" {
						error-message "pir must be greater than or equal to cir";
					}
					type uint64;
                    default 0;
					description
						"Peak information rate for the dual-rate token bucket
						policer.  This value represents the rate at which tokens
						are added to the secondary bucket.";
				}

				leaf pbs {
					must "((current()/../pir) and (current()/../pir > 0))" {
						error-message "pbs can't be configured without pir.";
					}
					must "((not(current()/../cbs)) or (current() >= current()/../cbs))" {
						error-message "pbs must be greater than or equal to cbs";
					}
					type uint64;
                    default 0;
					description
						"Excess burst size for the dual-rate token bucket policer.
						This value represents the depth of the secondary bucket.";
				}
				
				leaf green_action {
                    type stypes:copp_packet_action;
                    default "forward";
					description "Green action";
				}
				
				leaf yellow_action {
                    type stypes:copp_packet_action;
                    default "forward";
					description "Yellow action";
				}

				leaf red_action {
                    type stypes:copp_packet_action;
                    default "forward";
					description "Red action";
				}
				
				leaf genetlink_name {
					type string {
						pattern "(psample)" {
							error-message "Invalid value passed for genetlink_name";
						}
					}
					description
						"genetlink name";
				}
				
				leaf genetlink_mcgrp_name {
					type string {
						pattern "(packets)" {
							error-message "Invalid value passed for genetlink_mcgrp_name";
						}
					}
					description
						"genetlink multicast group name";
				}
			}
			/* end of list COPP_GROUP_LIST */
		}
		/* end of container COPP_GROUP */

		container COPP_TRAP {
			list COPP_TRAP_LIST {
				key name;

				leaf name {
					type string;
					description "Control plane policing trap name";
				}

				leaf-list trap_ids {
                    type enumeration {
                        enum stp;
                        enum lacp;
                        enum eapol;
                        enum lldp;
                        enum pvrst;
                        enum igmp_query;
                        enum igmp_leave;
                        enum igmp_v1_report;
                        enum igmp_v2_report;
                        enum igmp_v3_report;
                        enum sample_packet;
                        enum switch_cust_range;
                        enum arp_req;
                        enum arp_resp;
                        enum dhcp;
                        enum ospf;
                        enum pim;
                        enum vrrp;
                        enum bgp;
                        enum dhcpv6;
                        enum ospfv6;
                        enum vrrpv6;
                        enum bgpv6;
                        enum neigh_discovery;
                        enum mld_v1_v2;
                        enum mld_v1_report;
                        enum mld_v1_done;
                        enum mld_v2_report;
                        enum ip2me;
                        enum ssh;
                        enum snmp;
                        enum router_custom_range;
                        enum l3_mtu_error;
                        enum ttl_error;
                        enum udld;
                        enum bfd;
                        enum bfdv6;
                        enum src_nat_miss;
                        enum dest_nat_miss;
                        enum ptp;
                        enum pim;
                        enum arp_suppress;
                        enum nd_suppress;
                        enum icmp;
                        enum icmpv6;
                        enum iccp;
                        enum dhcp_l2;
                        enum dhcpv6_l2;
                    }
                    description "list of trap_ids";
				}

				leaf trap_group {
					type leafref {
						path "/sonic-copp/COPP_GROUP/COPP_GROUP_LIST/name";
					}
					description "reference to CoPP group";
				}
			}
			/* end of list COPP_TRAP_LIST */
		}
		/* end of container COPP_TRAP */
	}
	/* end of top level container */

	rpc get-match-protocols {
		description
			"RPC to get allowed match protocols";

		output {
			list Match_protocols {
				key "Protocol";

				leaf Protocol {
					type string;
					description
						"Protocol name";
				}
			}
		}
	}
	/* end of rpc get-match-protocols */
}
/* end of module sonic-copp */
