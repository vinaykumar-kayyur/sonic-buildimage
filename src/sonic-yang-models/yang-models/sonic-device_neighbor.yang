module sonic-device_neighbor {

    yang-version 1.1;

    namespace "http://github.com/Azure/sonic-device_neighbor";
    prefix device_neighbor;

    import ietf-inet-types {
        prefix inet;
    }

    import sonic-extension {
        prefix ext;
        revision-date 2019-07-01;
    }

    import sonic-port {
        prefix port;
        revision-date 2019-07-01;
    }

    description "DEVICE_NEIGHBOR YANG Module for SONiC OS";

    revision 2020-04-10 {
        description "First Revision";
    }

    container sonic-device_neighbor {

        container DEVICE_NEIGHBOR {

            description "DEVICE_NEIGHBOR part of config_db.json";

            list DEVICE_NEIGHBOR_LIST {

                key "peer_name";

                leaf peer_name {
                    type string {
                        length 1..255;
                    }
                }

                leaf name {
                    type string {
                        length 1..255;
                    }
                }

                leaf mgmt_addr {
                    type inet:ip-address;
                }

                leaf local_port {
                    type leafref {
                        path /port:sonic-port/port:PORT/port:PORT_LIST/port:name;
                    }
                }

                leaf port {
                    type string {
                        length 1..255;
                    }
                }

                leaf type {
                    type string {
                        length 1..255;
                    }
                }
            }
            /* end of list DEVICE_NEIGHBOR_LIST */
        }

        container DEVICE_NEIGHBOR_METADATA {

            description "DEVICE_NEIGHBOR_METADATA part of config_db.json";

            list DEVICE_NEIGHBOR_METADATA_LIST {

                key "peer_name";

                leaf peer_name {
                    type string {
                        length 1..255;
                    }
                }

                leaf hwsku {
                    type string {
                        length 1..255;
                    }
                }

                leaf lo_addr {
                    type string {
                        length 1..255;
                    }
                }

                leaf mgmt_addr {
                    type inet:ip-address;
                }

                leaf type {
                    type string {
                        length 1..255;
                    }
                }
            }
            /* end of list DEVICE_NEIGHBOR_LIST */
        }
        /* end of container DEVICE_NEIGHBOR */
	}
	/* end of top level container */
}
/* end of module sonic-device_neighbor */
