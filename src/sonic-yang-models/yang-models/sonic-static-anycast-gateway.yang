module sonic-static-anycast-gateway {

    yang-version 1.1;

    namespace "http://github.com/Azure/sonic-static-anycast-gateway";
    prefix sag;

    import ietf-yang-types {
        prefix yang;
    }

    description "SAG yang Module for SONiC OS";

    revision 2021-10-20 {
        description
            "Initial version";
    }

    container sonic-static-anycast-gateway {
        container SAG {
            container GLOBAL {
                description "Global static anycast gateway configuration";

                leaf gateway_mac {
                    type yang:mac-address;
                }
            }
        }
    }
}
