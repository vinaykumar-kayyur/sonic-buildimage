module sonic-mgmt-port {

    yang-version 1.1;

    namespace "http://github.com/Azure/sonic-mgmt-port";
    prefix mgmtprt;

    import sonic-types {
        prefix stypes;
    }

    description "MANAGEMENT PORT yang Module for SONiC OS";

    revision 2019-11-13 {
        description "First Revision";
    }

    container sonic-mgmt-port {

        container MGMT_PORT {

            description "MANAGEMENT PORT part of config_db.json";

            list MGMT_PORT_LIST {

                key "name";

                leaf name {
                    type string {
                        pattern 'eth([1-3][0-9]{3}|[1-9][0-9]{2}|[1-9][0-9]|[0-9])';
                    }
                }

                leaf speed {
                    type uint64 {
                        range "10|100|1000"; 
                    }
                }

                leaf autoneg {
                    type boolean;
                    default true;
                }

                leaf alias {
                    type string;
                }

                leaf description {
                    type string;
                }

                leaf mtu{
                    type uint32 {
                        range "1500..9216"; 
                    }
                    default 1500;
                }

                leaf admin_status {
                    type stypes:admin_status;
                    default up;
                }

            } /* end of list MGMT_PORT_LIST */

        } /* end of container MGMT_PORT */

    } /* end of container sonic-mgmt-port */

} /* end of module sonic-mgmt-port */
