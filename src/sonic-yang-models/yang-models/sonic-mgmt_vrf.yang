module sonic-mgmt-vrf {

    yang-version 1.1;

    namespace "http://github.com/Azure/sonic-mgmt-vrf";
    prefix mvrf;

    description
        "SONiC MGMT VRF";

    revision 2019-10-08 {
        description
            "First revision";
    }

    container sonic-mgmt-vrf {
        container MGMT_VRF_CONFIG {

            container vrf_global {

                leaf mgmtVrfEnabled {
                    type boolean;
                    default false;
                }

            } /* end of container vrf_global */

        } /* end of container MGMT_VRF_CONFIG */

    } /* end of container sonic-mgmt-vrf */

} /* end of module sonic-mgmt-vrf */
