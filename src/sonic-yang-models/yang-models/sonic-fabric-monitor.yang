module sonic-fabric-monitor{

    yang-version 1.1;

    namespace "http://github.com/sonic-net/sonic-fabric-monitor";
    prefix fabric-monitor;

    description "FABRIC_MONITOR yang Module for SONiC OS";

    revision 2023-03-14 {
        description "First Revision";
    }

    container sonic-fabric-monitor {

        container FABRIC_MONITOR {

            description "FABRIC_MONITOR part of config_db.json";

            container FABRIC_MONITOR_DATA {

                leaf monErrThreshCrcCells {
                    type uint32;
                    default 1;
                    description "The number of cells with errors.";
                }

                leaf monErrThreshRxCells {
                    type uint32;
                    default 61035156;
                    description "The number of cells received. If more than monErrThreshCrcCells out of monErrThreshRxCells seen with errors, the fabric port needs to be isolated";
                }

                leaf monPollThreshIsolation {
                    type uint8 {
                        range 1..10;
                    }
                    default 1;
                    description "Consecutive polls with higher error rate for isolation.";
                }

                leaf monPollThreshRecovery {
                    type uint8 {
                        range 1..10;
                    }
                    default 8;
                    description "Consecutive polls with lesser error rate for inclusion.";
                }

                leaf monCapacityThreshWarn {
                    type uint8 {
                        range 5..100;
                    }
                    default 10;
                    description "Percentage of up fabric links.";
                }

                leaf monState {
                    description "Configuration to set fabric link monitoring state: enable/disable";
                    type stypes:mode-status;
                    default disable;
                }

            } /* end of container FABRIC_MONITOR_DATA */

        } /* end of container FABRIC_MONITOR */

    } /* end of container sonic-fabric-monitor */

} /* end of module sonic-fabric-monitor */
