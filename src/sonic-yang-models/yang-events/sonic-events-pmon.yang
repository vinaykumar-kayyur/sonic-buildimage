module sonic-events-pmon {
    namespace "http://github.com/sonic-net/sonic-events-pmon";
    yang-version 1.1;
    prefix events-pmon;

    import openconfig-alarm-types {
        prefix oc-alarm-types;
    }
    import sonic-events-common {
        prefix evtcmn;
        revision-date 2022-12-01;
    }
    revision 2022-12-01 {
        description "pmon alert events.";
    }

    organization
        "SONiC";
    contact
        "SONiC";
    description
        "SONIC pmon events";

    container sonic-events-pmon {
        container pmon-exited {
            oc-alarm-types:MAJOR

            description "
                Declares an event reportes by pmon for an unexpected exit.
                The exited entity is the only param";

            leaf entity {
                type string;
                description "entity that had unexpected exit";
            }

            uses evtcmn:sonic-events-cmn;
        }
    }
}
