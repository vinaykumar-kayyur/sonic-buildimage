module sonic-events-swss {
    namespace "http://github.com/sonic-net/sonic-events-swss";
    yang-version 1.1;
    prefix events-swss;

    import openconfig-alarm-types {
        prefix oc-alarm-types;
    }
    import sonic-events-common {
        prefix evtcmn;
        revision-date 2022-12-01;
    }
    import sonic-types {
        prefix stypes;
    }
    revision 2022-12-01 {
        description "SWSS alert events.";
    }

    organization
        "SONiC";
    contact
        "SONiC";
    description
        "SONIC SWSS events";

    container sonic-events-swss {
        container if-state {
            oc-alarm-types:MINOR

            description "
                Declares an event for i/f flap. 
                The name of the flapping i/f and status are the only params.";

            leaf ifname {
                type leafref {
                    path "/port:sonic-port/port:PORT/port:PORT_LIST/port:name";
                }
                description "Interface name";
            } 

            leaf status {
                type stypes:admin_status;
                description "Provides the status as up (true) or down (false)";
            }

            uses evtcmn:sonic-events-cmn;
        }

        container pfc-storm {
            oc-alarm-types:MAJOR

            description "
                Declares an event for PFC storm.
                The name of the i/f facing the storm is the only param.";

            leaf ifname {
                type leafref {
                    path "/port:sonic-port/port:PORT/port:PORT_LIST/port:name";
                }
                description "Interface name";
            }

            leaf queue_index {
                type uint8;
            }

            leaf queue_id {
                type uint64_t;
            }

            leaf port_id {
                type uint64_t;
            }

            uses evtcmn:sonic-events-cmn;
        }

        container chk_crm_threshold {
            oc-alarm-types:MAJOR

            description "
                Declares an event for CRM threshold.";

            leaf percent {
                type uint8 {
                    range "0..100" {
                        error-message "Invalid percentage value";
                    }
                }
                description "percentage used";
            }

            leaf used_cnt {
                type uint8;
            }

            leaf free_cnt {
                type uint64_t;
            }

            uses evtcmn:sonic-events-cmn;
        }
    }
}
