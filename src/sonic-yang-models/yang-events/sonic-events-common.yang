module sonic-events-common {
    namespace "http://github.com/Azure/sonic-events-common";
    prefix evtcmn;
    yang-version 1.1;

    organization
        "SONiC";
    contact
        "SONiC";
    description
        "SONIC Events common definition";
    revision 2022-12-01 {
        description
            "Common reusable definitions";
    }

    grouping sonic-events-cmn {
        leaf timestamp {
            type yang::date-and-time;
            description "time of the event";
        }
    }

    grouping sonic-events-usage {
        leaf usage {
            type uint8 {
                range "0..100" {
                    error-message "Incorrect val for %";
                }
            }
            description "Percentage in use";
        }
        
        leaf limit {
            type uint8 {
                range "0..100" {
                    error-message "Incorrect val for %";
                }
            }
            description "Percentage limit set";
        }
    }

    identity EVENT_SEVERITY {
        description
            "Base identity for event severities. Severities 2-4
            are supported";
    }

    identity EVENT_SEVERITY_2 {
        base EVENT_SEVERITY;
        description
            "Indicates that the severity level of this type of event is 2";
    }

     identity EVENT_SEVERITY_3 {
        base EVENT_SEVERITY;
        description
            "Indicates that the severity level of this type of event is 3";
    }

     identity EVENT_SEVERITY_4 {
        base EVENT_SEVERITY;
        description
            "Indicates that the severity level of this type of event is 4";
    }
}
