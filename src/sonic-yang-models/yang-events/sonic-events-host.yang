module sonic-events-host {
    namespace "http://github.com/sonic-net/sonic-events-host";
    yang-version 1.1;
    prefix events-host;

    import openconfig-alarm-types {
        prefix oc-alarm-types;
    }
    import sonic-events-common {
        prefix evtcmn;
        revision-date 2022-12-01;
    }
    revision 2022-12-01 {
        description "BGP alert events.";
    }

    container sonic-events-host {
        container disk-usage {
            oc-alarm-types:MINOR

            description "
                Declares an event for disk usage crossing set limit
                The parameters describe the usage & limit set.";
            
            leaf fs {
                type string;
                description "Name of the file system";
                default "";
            }

            uses evtcmn:sonic-events-usage;

            uses evtcmn:sonic-events-cmn;
        }

        container memory-usage {
            oc-alarm-types:MINOR

            description "
                Declares an event for memory usage crossing set limit
                The parameters describe the usage & limit set.";
            
            uses evtcmn:sonic-events-usage;

            uses evtcmn:sonic-events-cmn;
        }

        container cpu-usage {
            oc-alarm-types:MINOR

            description "
                Declares an event for memory usage crossing set limit
                The parameters describe the usage & limit set.";
            
            uses evtcmn:sonic-events-usage;

            uses evtcmn:sonic-events-cmn;
        }

        container event-sshd {
            oc-alarm-types:MINOR

            description "
                Declares an event reported by sshd.
                This implies an internal system state blocks sshd from
                creating the new user.";

            leaf username {
                type string;
                description "Name of the new user";
            }

            uses evtcmn:sonic-events-cmn;
        }

        container event-disk {
            oc-alarm-types:MINOR

            description "
                Declares an event reported by disk check.
                The fail type declares the type of failure.
                read-only - denotes that disk is in RO state.";

            leaf fail_type {
                type enumeration {
                    enum "read_only";
                }
                description "Type of failure";
            }

            uses evtcmn:sonic-events-cmn;
        }

        container event-kernel {
            oc-alarm-types:MINOR

            description "
                Declares an event reported by kernel.
                The fail type declares the type of failure.";

            leaf fail_type {
                type enumeration {
                    enum "write_failed";
                    enum "write_protected";
                    enum "remount_read_only";
                    enum "aufs_read_lock";
                    enum "invalid_freelist";
                    enum "zlib_decompress";
                }
                description "Type of failure";
            }

            leaf msg {
                type string;
                description "human readable hint text";
                default "";
            }

            uses evtcmn:sonic-events-cmn;
        }

        container event-down-ctr {
            eventcmn:EVENT_SEVERITY_2

            description "
                Declares an container that is expected to be up is down.
                Reported by monit periodically.";
               
            leaf ctr_name {
                type string;
                description "Name of the container not running";
                default "";
            }

            uses evtcmn:sonic-events-cmn;
        }

        container event-stopped-ctr {
            eventcmn:EVENT_SEVERITY_2

            description "
                Declare an event at the time point of container stopping.
                event-down-ctr fires periodically until it starts up.";
               
            leaf ctr-name {
                type string;
                description "Name of the container";
                default "";
            }

            uses evtcmn:sonic-events-cmn;
        }

        container event-platform {
            evtcmn:EVENT_SEVERITY_2

            description "
                Declares an event for platform related failure.
                Params: 
                    fail_type provides the type of failure.";
               
            leaf fail_type {
                type enumeration {
                    enum "watchdog_timeout";
                    enum "switch_parity_error";
                    enum "SEU_error";
                }
                description "Type of failure";
            }

            uses evtcmn:sonic-events-cmn;
        }
    }
}
